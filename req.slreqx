# req

## req!Sheet1: References to req.xlsx (Sheet1) (Container)
Read-only references to Microsoft Excel document.

### $A2: Trun on LEDs (Functional)
If the led state is off, turn on each LED with it's related local pole. But if it's already turned on then it should not change

### $A3: Trun off LEDs (Functional)
If the led state is on turn off each LED with it's related local pole. But if it's already turned off then it should not change

### $A4: Send state based on device selector (Functional)
Each slave should send their states to the master periodically if their device selector is on

### $A5: Trun on a slave device selector (Functional)
Master trun on a slave device selector and trun off the others

### $A6: Turn off other slaves (Functional)
When a slave is selected, the others should be turned off

### $A7: Trun on LEDs from master (Functional)
Master can trun on the leds of the slave that it's device selector is on. if it's already turned on then it should not change

### $A8: Trun off LEDs from master (Functional)
Master can trun off the leds of the slave that it's device selector is on. if it's already turned off then it should not change
